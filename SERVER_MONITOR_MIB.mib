-- =============================================================================
-- SERVER-MONITOR-MIB
-- SNMP Management Information Base for Server Room Monitoring
-- Enterprise OID: 1.3.6.1.4.1.9999
-- =============================================================================

SERVER-MONITOR-MIB DEFINITIONS ::= BEGIN

IMPORTS
    OBJECT-TYPE, Integer32, NOTIFICATION-TYPE, enterprises
        FROM SNMPv2-SMI
    MODULE-IDENTITY
        FROM SNMPv2-SMI;

-- ---------------------------------------------------------------------------
-- Module Identity
-- ---------------------------------------------------------------------------
serverMonitorMIB MODULE-IDENTITY
    LAST-UPDATED "202603310000Z"
    ORGANIZATION "Server Room Operations"
    CONTACT-INFO "admin@example.com"
    DESCRIPTION  "MIB for monitoring server room environment via SNMP."
    REVISION     "202603310000Z"
    DESCRIPTION  "Initial version."
    ::= { enterprises 9999 }

-- ---------------------------------------------------------------------------
-- Enterprise root object
-- Base OID: 1.3.6.1.4.1.9999
-- ---------------------------------------------------------------------------
serverMonitor OBJECT IDENTIFIER ::= { enterprises 9999 }

-- ---------------------------------------------------------------------------
-- MIB Object Definitions
-- ---------------------------------------------------------------------------

-- Object 1: Server Room Temperature
temperature OBJECT-TYPE
    SYNTAX      Integer32
    MAX-ACCESS  read-only
    STATUS      current
    DESCRIPTION "Server room temperature in degrees Celsius.
                 Source: Open-Meteo Weather API (real-time).
                 OID: 1.3.6.1.4.1.9999.1.0"
    ::= { serverMonitor 1 }

-- Object 2: Server Room Humidity
humidity OBJECT-TYPE
    SYNTAX      Integer32
    MAX-ACCESS  read-only
    STATUS      current
    DESCRIPTION "Server room relative humidity as a percentage (0-100).
                 Source: Open-Meteo Weather API (real-time).
                 OID: 1.3.6.1.4.1.9999.2.0"
    ::= { serverMonitor 2 }

-- Object 3: Air Conditioning Status
acStatus OBJECT-TYPE
    SYNTAX      Integer32
    MAX-ACCESS  read-only
    STATUS      current
    DESCRIPTION "Air conditioning unit status.
                 1 = ON  (temperature >= AC_ON_THRESHOLD)
                 0 = OFF (temperature <  AC_ON_THRESHOLD)
                 OID: 1.3.6.1.4.1.9999.3.0"
    ::= { serverMonitor 3 }

-- Object 4: Cooling Fan Status
fanStatus OBJECT-TYPE
    SYNTAX      Integer32
    MAX-ACCESS  read-only
    STATUS      current
    DESCRIPTION "Server room cooling fan status.
                 1 = ON  (temperature >= FAN_ON_THRESHOLD)
                 0 = OFF (temperature <  FAN_ON_THRESHOLD)
                 OID: 1.3.6.1.4.1.9999.4.0"
    ::= { serverMonitor 4 }

-- Object 5: Alert Status
alertStatus OBJECT-TYPE
    SYNTAX      Integer32
    MAX-ACCESS  read-only
    STATUS      current
    DESCRIPTION "Composite alert status for the server room.
                 1 = ALERT  (temperature >= ALERT_THRESHOLD OR humidity >= HUMIDITY_THRESHOLD)
                 0 = NORMAL (all values within safe range)
                 OID: 1.3.6.1.4.1.9999.5.0"
    ::= { serverMonitor 5 }

-- ---------------------------------------------------------------------------
-- Notification (Trap) Definitions
-- ---------------------------------------------------------------------------
serverMonitorNotifications OBJECT IDENTIFIER ::= { serverMonitor 0 }

temperatureAlertTrap NOTIFICATION-TYPE
    OBJECTS     { temperature, humidity, alertStatus }
    STATUS      current
    DESCRIPTION "Trap sent when temperature exceeds the alert threshold."
    ::= { serverMonitorNotifications 1 }

humidityAlertTrap NOTIFICATION-TYPE
    OBJECTS     { humidity, temperature, alertStatus }
    STATUS      current
    DESCRIPTION "Trap sent when humidity exceeds the alert threshold."
    ::= { serverMonitorNotifications 2 }

normalStatusTrap NOTIFICATION-TYPE
    OBJECTS     { temperature, humidity, alertStatus }
    STATUS      current
    DESCRIPTION "Trap sent when server room returns to normal status."
    ::= { serverMonitorNotifications 3 }

END

-- =============================================================================
-- OID Summary Table
-- =============================================================================
-- Object            OID                          Type      Access
-- ---------------------------------------------------------------------------
-- serverMonitor     1.3.6.1.4.1.9999             BASE      -
-- temperature       1.3.6.1.4.1.9999.1.0         Integer32 read-only
-- humidity          1.3.6.1.4.1.9999.2.0         Integer32 read-only
-- acStatus          1.3.6.1.4.1.9999.3.0         Integer32 read-only
-- fanStatus         1.3.6.1.4.1.9999.4.0         Integer32 read-only
-- alertStatus       1.3.6.1.4.1.9999.5.0         Integer32 read-only
-- tempAlertTrap     1.3.6.1.4.1.9999.0.1         TRAP      notify
-- humidAlertTrap    1.3.6.1.4.1.9999.0.2         TRAP      notify
-- normalTrap        1.3.6.1.4.1.9999.0.3         TRAP      notify
